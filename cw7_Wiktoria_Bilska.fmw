FME workspace cw7_Wiktoria_Bilska.fmw
Startup Python:
      import fme
      import fmeobjects
      import smtplib
      import datetime

      from email.message import EmailMessage

      data = datetime.datetime.now().strftime("%I:%M%p on %d %B, %Y")
      email = fme.macroValues['e-mail']
      password = fme.macroValues['haslo']
      powiat = fme.macroValues['powiat']
      mailklient = fme.macroValues['e-mail_klienta']

      msg = EmailMessage()
      msg['Subject'] = 'Informacja o przetwarzanie FME'
      msg['From'] = email
      msg['To'] = mailklient
      msg.set_content('Drogi użytkowniku '+mailklient+', o godzinie '+data+' rozpoczęto przetwarzanie danych dla powiatu '+powiat)

      with smtplib.SMTP_SSL('smtp.gmail.com',465) as smtp:
          smtp.login(email,password)
          smtp.send_message(msg)
Shutdown Python:
      import fme
      import fmeobjects
      import smtplib
      import datetime

      from email.message import EmailMessage

      datakoniec = datetime.now()
      czas = datakoniec - data

      email = fme.macroValues['email']
      password = fme.macroValues['password']
      mailklient= fme.macroValues['e-mail_klienta']
      data = fme.macroValues['Data_początkowa']
      datakoniec = fme.macroValues['Data_koncowa']
      chmury = fme.macroValues['Max_pokrycie_chmurami']
      powiat = fme.macroValues['powiat']
      msg = EmailMessage()
      msg['Subject'] = 'Informacja o zakonczeniu przetwarzania'
      msg['From'] = email
      msg['To'] = mailklient


      if fme.status ==0:
          msg.set_content('Proces został przerwany ze względu na brak zobrazowań satelitarnych spełniających kryteria: powiat ' + powiat + ', pokrycie chmurami  '+
          chmury+', data początkowa '+ data + ', data końcowa '+ datakoniec)

          with open("C:\Users\Wiktoria\Desktop\5semestr\BD_przestrzennych\cw7\log.json",'w') as log:
              json.dump(fmeErrors,log)

          with open("C:\Users\Wiktoria\Desktop\5semestr\BD_przestrzennych\cw7\log.json",'rb') as file:
              file_data = file.read()
              file_name = "logs.json"

          msg.add_attachment(file_data, maintype='application', subtype='json', filename=file_name)

      else:
          msg.set_content('Czas przetwarzania ' + str(czas))
          with open("C:\Users\Wiktoria\Desktop\5semestr\BD_przestrzennych\cw7\Powiat_statystyki.csv",'rb') as file2:
              file2_data = file2.read()
              file2_name = "Powiat_statystyki.csv"

          msg.add_attachment(file2_data, maintype='application', subtype='csv', filename=file2_name)

          with open("C:\Users\Wiktoria\Desktop\5semestr\BD_przestrzennych\cw7\Powiat_NDVI_TIFF.tif",'rb') as file:
              file_data = file.read()
              file_name = "Powiat_NDVI_TIFF.tif"

          msg.add_attachment(file_data, maintype='image', subtype='tif', filename=file_name)


      with smtplib.SMTP_SSL('smtp.gmail.com', 465) as smtp:
          smtp.login(email, password)
          smtp.send_message(msg)

Parameters:
- e-mail = orzeszek.1.5.0@gmail.com   # Podaj e-mail
- haslo =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   # Wpisz hasło
- e-mail_klienta = orzeszek.1.5.0@gmail.com   # Podaj adres e-mail klienta
- powiat = powiat krakowski   # Wpisz nazwę powiatu
- Max_pokrycie_chmurami = 90
- Data_początkowa = 20201208   # "{}" Podaj datę początkową
- Data_koncowa = 20201208   # "{}" Podaj date koncowa
- SourceDataset_SHAPEFILE = $(FME_MF_DIR)Powiaty\Powiaty.shp   # Source Esri Shapefile(s)
- DestDataset_CSV2 = C:\Users\Wiktoria\Desktop\5semestr\BD_przestrzennych\cw7   # Destination CSV (Comma Separated Value) Folder
- DestDataset_TIFF = C:\Users\Wiktoria\Desktop\5semestr\BD_przestrzennych\cw7   # Destination TIFF (Tagged Image File Format) Folder

Readers:
- SHAPEFILE_1: SHAPEFILE from $(SourceDataset_SHAPEFILE) in EPSG:4258

Writers:
- CSV2_1: CSV2 to $(DestDataset_CSV2)
- TIFF_1: TIFF to $(DestDataset_TIFF)

Powiaty (reader SHAPEFILE_1)
    attributes: JPT_SJR_KO char(3), JPT_KOD_JE char(20), JPT_NAZWA_ char(128), JPT_ORGAN_ char(254), JPT_JOR_ID long, WERSJA_OD date, WERSJA_DO date, WAZNY_OD date, WAZNY_DO date, JPT_KOD__1 char(3), JPT_NAZWA1 char(3), JPT_ORGAN1 char(3), JPT_WAZNA_ char(3), ID_BUFORA_ double, ID_BUFORA1 double, ID_TECHNIC long, IIP_PRZEST char(20), IIP_IDENTY char(128), IIP_WERSJA char(32), JPT_KJ_IIP char(20), JPT_KJ_I_1 char(128), JPT_KJ_I_2 char(32), JPT_OPIS char(254), JPT_SPS_KO char(3), ID_BUFOR_1 long, JPT_ID long, JPT_KJ_I_3 char(3), Shape_Leng double, Shape_Area double
    -> Tester
Tester
    BOOL_OP = OR
    COMPOSITE_TEST = 1
    TEST_CLAUSE = CASE_INSENSITIVE_TEST @Value(JPT_NAZWA_) CONTAINS_REGEX $(powiat)
    TEST_MODE = CASE_INSENSITIVE_TEST
    PASSED -> SentinelDownloader [Initiator]
    PASSED -> Clipper [CLIPPER]
SentinelDownloader
    BEGIN = $(Data_początkowa)
    Band_Resolution = 10m
    CloudCover = $(Max_pokrycie_chmurami)
    END = $(Data_koncowa)
    LEVEL = Level 2A
    key_name = wbilska99
    key_pw =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
    platform = Sentinel-2
    zip_output = $(FME_MF_DIR)sentinel.zip
    Band_4 -> Sampler
    Band_8 -> Sampler_2
Sampler
    RATE = 1
    SAMPLE_MODE = No
    SAMPLE_TYPE_LONG = Every Nth Feature
    SAMPLED -> NDVICalculator [Red]
Sampler_2
    RATE = 1
    SAMPLE_MODE = No
    SAMPLE_TYPE_LONG = Every Nth Feature
    SAMPLED -> NDVICalculator [Infrared]
NDVICalculator
    COLORIZE = Blue-Yellow-Green Palette
    INDEXTYPE = NDVI
    SAVIADJUSTMENT = 0.5
    -> Reprojector
Reprojector
    DEST = LL-ETRF89
    INTERPOLATION_TYPE_NAME = Nearest Neighbor
    RASTER_CELL_SIZE = Preserve Cells
    RASTER_TOLERANCE = 0.0
    SOURCE = Read from feature
    REPROJECTED -> Clipper [CLIPPEE]
Clipper
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> RasterStatisticsCalculator
    INSIDE -> Powiat_NDVI_TIFF (writer TIFF_1)
RasterStatisticsCalculator
    RASTER_LEVEL = BAND_ONLY
    RASTER_STATS = "0   MEAN   STDEV  "
    -> Powiat_statystyki (writer CSV2_1)
Powiat_statystyki (writer CSV2_1)
    attributes: _clipped string, band0.mean real64, band0.stdev real64
Powiat_NDVI_TIFF (writer TIFF_1)
    attributes: _clipped char(200)

FME custom transformer ZipExtractor
Extracts files archived in a zip file, and then outputs features for every extracted file and directory.
    Each resulting feature has two attributes storing full path string of an extracted file/directory - 
    "path_unix"
    (UNIX style) and 
    "path_windows"
    (Windows style), and also has an attribute that indicates the depth of the file/directory in the extracted directory hierarchy - 
    "path_depth" 
    (integer starting from 1).
    The features containing file path will be output through the File port, and the features containing directory path will be output through the Directory port. 
    All the extracted files will be saved into a subfolder under the folder specified with the "Destination Root Folder" parameter. The subfolder name will be the same as the source zip file name without extension. For example, if the source zip file name is 
    "data.zip"
    and the specified root folder path is 
    "C:\root"
    , extracted files will be saved into 
    "C:\root\data"
    .
    If the same name folder exists under the specified root folder, a number will be added to the destination subfolder name as suffix to differentiate from the existing folder, by default. e.g. 
    "C:\root\data_1"
    , 
    "C:\root\data_2"
    , and so on. 
    If you set "Yes" to the "Replace Existing Destination Subfolder" parameter, the existing subfolder and all files within it will be removed, and then the destination subfolder will be created newly.
    By default, this transformer will NOT unzip zip files that are archived (nested) in the source zip file. If you set "Yes" to the "Unzip Nested Zip Files Recursively" parameter, this transformer unzips all the nested zip files recursively.
    All attributes of the input feature will be propagated to the output features, but the geometry and coordinate system will not be preserved.
    If the specified source zip file or destination root folder is invalid, the input feature will be output through the <Rejected> port.
    Note: The Unzipper (FME Hub) can also be used to unzip a zip file. The ZipExtractor may be useful if you need to specify the destination root folder and/or to unzip nested zip file(s).
Parameters
    Source Zip File
    :
    Specify a zip file that should be extracted. The zip file name has to end with the extension ".zip" (case insensitive) by default, but optionally, you can also specify any extension(s) which this transformer should attempt to extract as a zip file. See the Allowable Source/Nested Zip File Extensions parameter.
    Destination Root Folder
    :
    Specify a folder in which a subfolder containing all extracted files should be created. If you leave this parameter blank, this transformer treats the folder containing the source zip file as the destination root folder.
    All the extracted files will be saved into a subfolder under the root folder. The subfolder name will be the same as the source zip file name without extension. For example, if the source zip file name is 
    "data.zip"
    and the specified root folder path is 
    "C:\root"
    , extracted files will be saved into 
    "C:\root\data"
    .
    Replace Existing Destination Subfolder
    :
    By default, a number will be added to the destination subfolder name as suffix if the same name folder exists under the spcified root folder. e.g. 
    "C:\root\data_1"
    , 
    "C:\root\data_2"
    , and so on. If you set "Yes" to this parameter, the existing subfolder and all files within it will be removed, and then the destination subfolder will be created newly. 
    Unzip Nested Zip Files Recursively
    :
    By default, this transformer will NOT unzip zip files that are archived (nested) in the source zip file. If you set "Yes" to this parameter, this transformer unzips all the nested zip files recursively.
    Preserve Nested Zip Files
    :
    By default, zip files nested in the source zip file will be removed after unzipping them, when the "Unzip Nested Zip Files Recursively" parameter is set to "Yes". If you set "Yes" to this parameter, the nested zip files will also be preserved.
    This parameter affects the result only when the "Unzip Nested Zip Files Recursively" parameter is set to "Yes". When the "Unzip Nested Zip Files Recursively" is set to "No", nested zip files always will be preserved regardless of this parameter.
    Allowable Source/Nested Zip File Extension(s)
    :
    By default, this transformer accepts only zip files whose name end with the extension ".zip" (case insensitive). However, if you want to extract zip files with other extension, you can specify allowable extention(s) via these parameters, with space-separated format when specifying two or more.
    Here, "Source Zip File" means that the top level zip file which would be set to the Source Zip File parameter; "Nested Zip File"means that internal zip file(s) which have been archived within the source zip file.
    If you leave the parameter field blank (it's the default), only ".zip" (case insensitive) will be allowable as zip file extension.
    Note that "zip" won't be allowable if you have set one or more extension other than ".zip" to the parameter. If you want to allow ".zip" and other extension(s) simultaneously, specify all possible extensions including ".zip" with the parameter.
    The leading dot "." of extensions can be omitted.

Parameters:
- ZIP_PATH =   # Source Zip File
- ROOT_FOLDER =   # Destination Root Folder
- REPLACE = No   # Replace Existing Destination Subfolder
- RECURSIVE = No   # Unzip Nested Zip Files Recursively
- PRESERVE = No   # Preserve Nested Zip Files
- EXT_S =   # Allowable Source Zip File Extension(s)
- EXT_N =   # Allowable Nested Zip File Extension(s)

Input (input)
    -> ParameterFetcher
ParameterFetcher
    ATTR_LIST = __unzipper.zip_path {$(ZIP_PATH)} __unzipper.root_folder {$(ROOT_FOLDER)} __unzipper.replace {$(REPLACE)} __unzipper.recursive {$(RECURSIVE)} __unzipper.preserve {$(PRESERVE)} __unzipper.ext_s {$(EXT_S)} __unzipper.ext_n {$(EXT_N)}
    -> PythonCaller
PythonCaller
    HIDE_ATTRIBUTES = __unzipper.ext_n __unzipper.ext_s __unzipper.preserve __unzipper.recursive __unzipper.replace __unzipper.root_folder __unzipper.zip_path
    NEW_ATTRIBUTES = path_unix path_windows path_depth __unzipper.flag _error_message
    PYTHONSOURCE:
      # 2018-06-14,  Takashi Iijima,  Added Allowable Source/Nested Zip File Extention(s) parameter.
      # 2016-01-25,  Takashi Iijima,  Updated to trim leading and trailing whitespaces of specified path strings.
      # 2016-01-23,  Takashi Iijima,  Updated:
      # - added function to check file extension to prevent extracting non-archiver zip files. e.g. Excel (*.xlsx) etc.
      # - added codes to create desitnation root folder if it is specified but doesn't exist.
      # - added option to preserve nested zip files after unzipping them.
      # - added "path_depth" attribute to output features.
      # 2016-01-21,  Takashi Iijima,  Original Implementation

      import fmeobjects, zipfile, os

      class ZipExtractor(object):
          def __init__(self):
              self.logger = fmeobjects.FMELogFile()
              self.kFlagFile = 'file'
              self.kFlagDirectory = 'directory'
              self.kFlagReject = 'reject'
              self.kFlagTerminate = 'terminate'
              self.zipExtS = set(['.zip'])
              self.zipExtN = set(['.zip'])

          def isZipFileS(self, path):
              _, ext = os.path.splitext(path)
              return ext.lower() in self.zipExtS and zipfile.is_zipfile(path)

          def isZipFileN(self, path):
              _, ext = os.path.splitext(path)
              return ext.lower() in self.zipExtN and zipfile.is_zipfile(path)

          def input(self, feature):
              # Retrieve parameter values from feature attributes, then remove the attributes.
              # Zip path may end with a path separator if extracted by the FilenamePartExtractor as "_dirpath".
              zipPath = feature.getAttribute('__unzipper.zip_path').strip().rstrip('\\/')
              rootFolder = feature.getAttribute('__unzipper.root_folder').strip()
              replace = (feature.getAttribute('__unzipper.replace') == 'Yes')
              self.recursive = (feature.getAttribute('__unzipper.recursive') == 'Yes')
              self.preserve = (feature.getAttribute('__unzipper.preserve') == 'Yes')
              extS = set(feature.getAttribute('__unzipper.ext_s').split())
              extN = set(feature.getAttribute('__unzipper.ext_n').split())
              feature.removeAttrsWithPrefix('__unzipper.')

              if extS:
                  self.zipExtS = set([(e if e.startswith('.') else ('.%s' % e)).lower() for e in extS])
              if extN:
                  self.zipExtN = set([(e if e.startswith('.') else ('.%s' % e)).lower() for e in extN])

              # If destination root folder is specified but doesn't exist, try creating the directory.
              isRootValid = True
              if rootFolder and not os.path.exists(rootFolder):
                  try:
                      os.makedirs(rootFolder)
                  except:
                      isRootValid = False

              # If specified zip file or destination root folder is invalid, reject the input feature.
              if not os.path.exists(zipPath) or not self.isZipFileS(zipPath) or not isRootValid:
                  self.logger.logMessageString('Specified zip file or destination root folder is invalid.',  \
                      fmeobjects.FME_WARN)
                  feature.setAttribute('__unzipper.flag', self.kFlagReject)
                  self.pyoutput(feature)
                  return

              # Define destination folder path: <root folder>/<source zip file name without extension>
              # If root folder is not specified, treat the folder containing source zip file as root folder.
              zipPath = os.path.abspath(zipPath)
              zipFolder, zipName = os.path.split(zipPath)
              destFolder = os.path.join(os.path.abspath(rootFolder) if rootFolder else zipFolder, zipName[:-4])

              try:
                  # If the destination folder exists,
                  # - remove the existing folder and all files within it when REPLACE is set to Yes,
                  # - add suffix to the folder path when REPLACE is set to No.
                  if os.path.exists(destFolder):
                      if replace:
                          for dirpath, dirs, files in os.walk(destFolder, topdown=False):
                              for name in files:
                                  os.remove(os.path.join(dirpath, name))
                              for name in dirs:
                                  os.rmdir(os.path.join(dirpath, name))
                          os.rmdir(destFolder)
                      else:
                          format, n = '%s_%d', 1
                          while os.path.exists(format % (destFolder, n)): n += 1
                          destFolder = format % (destFolder, n)

                  # Extract the zip file and output features containing extracted file/directory path.
                  self.pathInfos = [] # tuples list - (file or directory path, flag: 'file' or 'directory', depth)
                  self.extract(zipPath, destFolder, 1)
                  for path, flag, depth in self.pathInfos:
                      feat = feature.cloneAttributes()
                      feat.setAttribute('path_unix', path.replace('\\', '/'))
                      feat.setAttribute('path_windows', path.replace('/', '\\'))
                      feat.setAttribute('path_depth', depth)
                      feat.setAttribute('__unzipper.flag', flag)
                      self.pyoutput(feat)

              except Exception as ex:
                  feature.setAttribute('_error_message', 'Unexpected error: %s' % ex)
                  feature.setAttribute('__unzipper.flag', self.kFlagTerminate)
                  self.pyoutput(feature)

          # Extract a zip file.
          def extract(self, zipPath, destPath, depth):
              with zipfile.ZipFile(zipPath) as z: z.extractall(destPath)
              self.findFiles(destPath, depth)

          # Find and collect extracted file/directory paths.
          def findFiles(self, dirPath, depth):
              self.pathInfos.append((dirPath, self.kFlagDirectory, depth))
              depth += 1
              for fname in os.listdir(dirPath):
                  path = os.path.join(dirPath, fname)
                  if os.path.isdir(path):
                      self.findFiles(path, depth)
                  elif self.recursive and self.isZipFileN(path):
                      if self.preserve:
                          self.pathInfos.append((path, self.kFlagFile, depth))
                          self.extract(path, os.path.join(dirPath, fname[:-4]), depth)
                      else:
                          self.extract(path, os.path.join(dirPath, fname[:-4]), depth)
                          os.remove(path)
                  else:
                      self.pathInfos.append((path, self.kFlagFile, depth))
    PYTHONSYMBOL = ZipExtractor
    -> AttributeFilter
AttributeFilter
    ATTR_NAME = __unzipper.flag
    ATTR_VALUES = file,directory,reject,terminate,<EMPTY>,<MISSING>,<NULL>,<UNFILTERED>
    file -> File (output)
    directory -> Directory (output)
    reject -> <Rejected> (output)
    terminate -> AttributeRemover
File (output)
Directory (output)
<Rejected> (output)
AttributeRemover
    REMOVE_ATTRS = __unzipper.flag,path_depth,path_unix,path_windows
    -> Terminator
Terminator
    MESSAGE = @Value(_error_message)

FME custom transformer SentinelDownloader
Description 
This transformer allows you to access the COPERNICUS Open Access Hub and download Sentinel-II images right from the source.
Since the existing Sentinel-II reader targets an "Requester pays" Amazon bucket, AWS credentials are required in addition to a charge per x requests or GB.
Using the con terra SentinelDownloader transformer, you only need a free account from COPERNICUS Open Access Hub to access the Sentinel-II data.  
If you have any question or if you are looking for professional services support, please contact fme@conterra.de. 
Configuration 
Input Port 
Initiator: 
An Area Of Interest (AOI) polygon feature OR 
A point feature (e.g. defined in the Creator transformer) OR 
A (textual) WKT representation of a point or polygon feature (e.g. POINT(7.6528 51.9352) )
Coordinates must be in LL84. 
Parameters/Properties 
KEY_NAME:
Please enter your user name from the COPERNICUS Open Access Hub 
KEY_ PW: 
Please enter your account password from the COPERNICUS Open Access Hub 
BEGIN [optional]: 
Choose the start date of your ingestion period 
END [optional]: 
Choose the end date of your ingestion period 
LEVEL: 
Choose between the two data product levels: Level 1C (Top of atmosphere reflectances, geometric and radiometric corrected) and Level 2A (Botton of atmosphere reflectances)
CLOUDCOVER [optional]: 
In this optional parameter, you can choose whether you want your results are filtered by a maximum cloud cover percentage. Keep in mind that this parameter could be the bottleneck of your search query as it possibly will exclude data if the parameter value is too small. 
BAND_RESOLUTION: 
Choose between the three possible spatial resolutions (ground sampling distance) 10m, 20m, 60m, and All. 
ZIP_OUTPUT: 
Set a location where the downloaded zip file is saved. Please regard to type in the ".zip" file format at the end of the folder name.
Output Ports 
The output depends on the choosen product Level and spatial resolution. For detailed information about a specific band, see this. 
Despite the choosen spatial resolution, the whole image stack (Level1C ~0.8GB / Level 2A ~1GB) will be downloaded from the COPERNICUS Open Access Hub and stored in the ZIP_OUTPUT destination folder. Users should consider deleting unnecessary data afterwards. 
Level 1C: 
10m 
Bands 2, 3, 4, and 8. 
20m 
Bands 5, 6, 7, 8A, 11, and 12. 
60m 
Bands 1, 9, and 10 
All 
All 13 bands at their best posible spatial resolution (see above) and the True Color Image (TCI) 
Level 2A: 
10m 
Bands 2, 3, 4, and 8. 
20m
Bands 2, 3, 4, 5, 6, 7, 8A, 11, and 12 (all bands in 20m spatial resolution) 
60m 
Bands 1, 2, 3, 4, 5, 6, 7, 8A, 9, 11, and 12 (all bands in 60m spatial resolution) 
All 
All 12 bands at their best posible spatial resolution (see above) and the True Color Image (TCI)

Parameters:
- key_name =   # User name (SciHub)
- key_pw =   # Password (SciHub)
- DATE = 20180101   # BEGIN "{}" Enter the start date of ingestion
- END = 20181231   # "{}" Enter the end of your ingestion period
- LEVEL = Level 2A   # "Level 1C"%"Level 2A" Product Level
- Band_Resolution =   # Please enter the desired spatial resolution
- CloudCover = 5   # Enter MAX Cloud Cover Percentage in %
- zip_output =   # Zip archive for downloaded data

Initiator (input)
    -> TextEncoder
Note: Generate API-Key from name:pw and Base64 encoding
Note: Placeholder S1
TextEncoder
    DEST_ATTR = _key_encoded
    ENCODING_TYPE = BASE64_ENCODE
    STRING_TO_ENCODE = $(key_name):$(key_pw)
    -> VariableSetter
VariableSetter
    SCOPE = Global
    VALUE = @Value(_key_encoded)
    VARNAME = key
    -> GeometryFilter
XMLFragmenter
    ATTRIBUTE_XML = _response_body
    EMBEDDED_EXPRESSIONS = entry
    FEATURE_TYPES_FORMAT_NAME = XML
    MERGE_ATTRS = No
    REJECT_FEATURES_WITH_NO_FRAGMENTS = YES
    XML_SOURCE_TYPE = Attribute with XML document
    FRAGMENTS -> Tester_2
    <REJECTED> -> Terminator_2
Band_1 (output)
Band_2 (output)
Band_3 (output)
Band_4 (output)
Band_5 (output)
Band_6 (output)
Band_7 (output)
Band_8 (output)
Band_8A (output)
Band_9 (output)
Band_10 (output)
Band_11 (output)
Band_12 (output)
TCI (output)
Note: Terminate the translation if no results were acquired
Terminator_2
    MESSAGE:
      Translation Terminated. There are zero search results with your parameters.
      To get results, please change the parameters, e.g. the ingestion date or the maximum cloud coverage percentage.

Bookmark: Downloading Sentinel-2 data
GeometryFilter
    BREAK_AGG = No
    GEOM_PORT_NAMES = Point Area Text
    POINT -> Reprojector
    AREA -> BoundingBoxReplacer
    TEXT -> AttributeCreator_3
    <UNFILTERED> -> Terminator
Note: Terminate the translation if an unexpected input exists
Terminator
    MESSAGE = Translation Terminated because none of the input parameters was either a point, polygon, or text (WKT) feature.

Bookmark: Spatial filter by point object
Reprojector
    DEST = LL-WGS84
    INTERPOLATION_TYPE_NAME = Nearest Neighbor
    RASTER_CELL_SIZE = Preserve Cells
    RASTER_TOLERANCE = 0.0
    SOURCE = Read from feature
    REPROJECTED -> CoordinateExtractor
CoordinateExtractor
    IND = 0
    MODE = Specify Coordinate
    X_ATTR = _x
    Y_ATTR = _y
    Z_ATTR = _z
    -> AttributeCreator
AttributeCreator
    ATTR_TABLE:
      SET_TO date_param = ingestionDate:[@DateTimeFormat($(BEGIN),%Y-%m-%d)T00:00:00.000Z TO @DateTimeFormat($(END),%Y-%m-%d)T23:59:00.000Z]
      SET_TO product_type = FME_CONDITIONAL:DEFAULT_VALUE'producttype:S2MSI2A'BOOL_OP;OR;COMPOSITE_TEST;<Unused>;TEST $(LEVEL) = Level 1C'producttype:S2MSI1C'FME_NUM_CONDITIONS2___
    -> HTTPCaller_3
Note: Select based on intersection with Point and platformname:Sentinel-2 and ingestion date
HTTPCaller_3
    CONNECTION_TIMEOUT_LENGTH = 60
    CUSTOM_HEADERS = Authorization;Basic @Value(_key_encoded)
    ERROR_ATTR = _error
    FOLLOW_REDIRECTS = Yes
    HTTP_METHOD = GET
    SAVE_FILE = Attribute
    STATUS_CODE_ATTR = _http_status_code
    TARGET_ATTR = _response_body
    TARGET_ATTR_ENCODING = auto-detect
    TARGET_URL = https://scihub.copernicus.eu/dhus/search?q=(footprint:"Intersects(@Value(_x) @Value(_y))" AND platformname:$(platform) AND @Value(product_type) AND @Value(date_param) AND cloudcoverpercentage:[0 TO $(CloudCover)])
    TRANSFER_TIMEOUT_LENGTH = 90
    USE_COOKIES = No
    VERIFY_SSL_CERTIFICATES = Yes
    -> XMLFragmenter

Bookmark: Spatial filter by Polygon object
BoundingBoxReplacer
    BOXTYPE = 2D Bounding Box
    BOX -> CoordinateExtractor_2
CoordinateExtractor_2
    LIST_NAME = coord
    MODE = All Coordinates
    -> AttributeCreator_2
AttributeCreator_2
    ATTR_TABLE:
      SET_TO date_param = ingestionDate:[@DateTimeFormat($(BEGIN),%Y-%m-%d)T00:00:00.000Z TO @DateTimeFormat($(END),%Y-%m-%d)T23:59:00.000Z]
      SET_TO poly = POLYGON((@Value(coord{0}.x) @Value(coord{0}.y),@Value(coord{1}.x) @Value(coord{1}.y),@Value(coord{2}.x) @Value(coord{2}.y),@Value(coord{3}.x) @Value(coord{3}.y),@Value(coord{4}.x) @Value(coord{4}.y)))
      SET_TO product_type = FME_CONDITIONAL:DEFAULT_VALUE'producttype:S2MSI2A'BOOL_OP;OR;COMPOSITE_TEST;<Unused>;TEST $(LEVEL) = Level 1C'producttype:S2MSI1C'FME_NUM_CONDITIONS2___
    -> HTTPCaller
Note: Select based on intersection with Polygon and platformname:Sentinel-2 and ingestion date
HTTPCaller
    CONNECTION_TIMEOUT_LENGTH = 60
    CUSTOM_HEADERS = Authorization;Basic @Value(_key_encoded)
    ERROR_ATTR = _error
    FOLLOW_REDIRECTS = Yes
    HTTP_METHOD = GET
    SAVE_FILE = Attribute
    STATUS_CODE_ATTR = _http_status_code
    TARGET_ATTR = _response_body
    TARGET_ATTR_ENCODING = auto-detect
    TARGET_URL = https://scihub.copernicus.eu/dhus/search?q=(footprint:"Intersects(@Value(poly))" AND platformname:$(platform)  AND @Value(product_type) AND @Value(date_param) AND cloudcoverpercentage:[0 TO $(CloudCover)])
    TRANSFER_TIMEOUT_LENGTH = 90
    USE_COOKIES = No
    VERIFY_SSL_CERTIFICATES = Yes
    -> XMLFragmenter

Bookmark: Spatial filter by Cordinates as Text
AttributeCreator_3
    ATTR_TABLE:
      SET_TO date_param = ingestionDate:[@DateTimeFormat($(BEGIN),%Y-%m-%d)T00:00:00.000Z TO @DateTimeFormat($(END),%Y-%m-%d)T23:59:00.000Z]
      SET_TO wkt_object = @Value(fme_text_string)
      SET_TO product_type = FME_CONDITIONAL:DEFAULT_VALUE'producttype:S2MSI2A'BOOL_OP;OR;COMPOSITE_TEST;<Unused>;TEST $(LEVEL) = Level 1C'producttype:S2MSI1C'FME_NUM_CONDITIONS2___
    -> TestFilter
TestFilter
    DEFAULT_VALUE = <UNFILTERED>
    TEST_LIST = "BOOL_OP,OR,COMPOSITE_TEST,""""""<Unused>"""""",TEST_CLAUSE,CASE_INSENSITIVE_TEST @Value(wkt_object) CONTAINS POINT",Point,"BOOL_OP,OR,COMPOSITE_TEST,""""""<Unused>"""""",TEST_CLAUSE,CASE_INSENSITIVE_TEST @Value(wkt_object) CONTAINS POLYGON",Polygon
    Point -> StringReplacer
    Polygon -> HTTPCaller_5
Note: Select based on intersection with WKT object and platformname:Sentinel-2 and ingestion date
HTTPCaller_5
    CONNECTION_TIMEOUT_LENGTH = 60
    CUSTOM_HEADERS = Authorization;Basic @Value(_key_encoded)
    ERROR_ATTR = _error
    FOLLOW_REDIRECTS = Yes
    HTTP_METHOD = GET
    SAVE_FILE = Attribute
    STATUS_CODE_ATTR = _http_status_code
    TARGET_ATTR = _response_body
    TARGET_ATTR_ENCODING = auto-detect
    TARGET_URL = https://scihub.copernicus.eu/dhus/search?q=(footprint:"Intersects(@Value(wkt_object))" AND platformname:$(platform)  AND @Value(product_type) AND @Value(date_param) AND cloudcoverpercentage:[0 TO $(CloudCover)])
    TRANSFER_TIMEOUT_LENGTH = 90
    USE_COOKIES = No
    VERIFY_SSL_CERTIFICATES = Yes
    -> XMLFragmenter

Bookmark: POINT replacer
StringReplacer
    CASE = NO
    FIND_TEXT = POINT(
    NO_MATCH = _FME_NO_OP_
    REGEXP = NO
    SRC_ATTRS = wkt_object
    -> StringReplacer_2
StringReplacer_2
    CASE = NO
    FIND_TEXT = )
    NO_MATCH = _FME_NO_OP_
    REGEXP = NO
    SRC_ATTRS = wkt_object
    -> HTTPCaller_5

Bookmark: Filtering the level of imagery
Note: Product level?
Tester_2
    BOOL_OP = AND
    TEST_CLAUSE = TEST $(LEVEL) = Level 2A
    TEST_MODE = TEST
    PASSED -> Tester
    FAILED -> Tester_6
Note: Filter L2A data
Tester
    BOOL_OP = AND
    TEST_CLAUSE = CASE_INSENSITIVE_TEST @Value(xml_fragment) CONTAINS _MSIL2A_
    TEST_MODE = TEST
    PASSED -> XMLFragmenter_2
    PASSED -> XMLFlattener
    FAILED -> Logger_2
Logger_2
    LOG_FEATURE = NONE
    MAXFEATS = 20
    MESSAGE = Unfortunately, there is no L2A data availabe. Try to choose the option "Level 1C" at the "Product Level" parameter.
    SEVERITY = WARN
Note: Filter L1C data
Tester_6
    BOOL_OP = AND
    TEST_CLAUSE = CASE_INSENSITIVE_TEST @Value(xml_fragment) CONTAINS _MSIL1C_
    TEST_MODE = TEST
    PASSED -> XMLFlattener_2
    PASSED -> XMLFragmenter_2
    FAILED -> Logger_3
Logger_3
    LOG_FEATURE = NONE
    MAXFEATS = 20
    MESSAGE = Unfortunately, the search results do not match the search criteria.
    SEVERITY = WARN

Bookmark: Download L2A data
XMLFlattener
    ATTRIBUTE_XML = xml_fragment
    EMBEDDED_EXPRESSIONS = link
    FEATURE_TYPES_FORMAT_NAME = XML
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    NEW_ATTRIBUTES = link.href
    XML_SOURCE_TYPE = Attribute with XML document
    -> VariableRetriever
VariableRetriever
    SCOPE = Global
    VALUE_ATTR = _keyAPI
    VARNAME = key
    -> HTTPCaller_2
Note: Download
HTTPCaller_2
    CONNECTION_TIMEOUT_LENGTH = 60
    CUSTOM_HEADERS = Authorization;Basic @Value(_keyAPI)
    ERROR_ATTR = _error
    FILE_PATH_ATTR = _response_file_path
    FOLLOW_REDIRECTS = Yes
    HTTP_METHOD = GET
    OUTPUT_FILENAME = $(zip_output)
    SAVE_FILE = File
    SAVE_MULTI = No
    STATUS_CODE_ATTR = _http_status_code
    TARGET_URL = @Value(link.href)
    TRANSFER_TIMEOUT_LENGTH = 90
    USE_COOKIES = No
    VERIFY_SSL_CERTIFICATES = Yes
    -> Junction

Bookmark: Write information to log file
XMLFragmenter_2
    ATTRIBUTE_XML = xml_fragment
    EMBEDDED_EXPRESSIONS = date[@name="ingestiondate"]
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes=""/>
    MERGE_ATTRS = Yes
    NEW_ATTRIBUTES = date
    REJECT_FEATURES_WITH_NO_FRAGMENTS = YES
    XML_SOURCE_TYPE = Attribute with XML document
    FRAGMENTS -> StatisticsCalculator
StatisticsCalculator
    COMPUTE_HISTOGRAM = NO
    COUNT_ATTR = _count
    PREPEND_ATTR_NAME_CHOICE = For multiple results only
    STATS_ATTRS = xml_matched_element
    SUMMARY -> FeatureMerger [REQUESTOR]
    COMPLETE -> ListBuilder
ListBuilder
    GROUPS_ORDERED = No
    LIST_ATTRS_TO_INCLUDE = date
    LIST_NAME = _datelist
    -> ListConcatenator
ListConcatenator
    DROP_EMPTY_PARTS = No
    LIST_ATTR = _datelist{}.date
    SEP = " & "
    VAL_ATTR = _concatenated
    -> FeatureMerger [SUPPLIER]
FeatureMerger
    ATTR_ACCUM_MODE = Merge Supplier
    ATTR_CONFLICT_RES = Use Requestor
    CLEANING_TOLERANCE = None
    CONNECT_Z_MODE = First Wins
    GEOM_TYPE = Build Polygons
    IGNORE_NULLS = No
    JOIN_KEYS = 1 1 AUTO
    MERGE_TYPE = Attributes Only
    PROCESS_DUPS = YES
    REJECT_NULL_MISSING_KEYS = No
    SUPPLIERS_FIRST = No
    MERGED -> Logger
Logger
    LOG_FEATURE = NONE
    MAXFEATS = 100
    MESSAGE:
      Your request delivers @Value(_count) result(s).
      The request delivers images at the following dates: @Value(_concatenated)
    SEVERITY = WARN

Bookmark: Download L1C data
XMLFlattener_2
    ATTRIBUTE_XML = xml_fragment
    EMBEDDED_EXPRESSIONS = link
    FEATURE_TYPES_FORMAT_NAME = XML
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    NEW_ATTRIBUTES = link.href
    XML_SOURCE_TYPE = Attribute with XML document
    -> VariableRetriever_2
VariableRetriever_2
    SCOPE = Global
    VALUE_ATTR = _keyAPI
    VARNAME = key
    -> HTTPCaller_4
Note: Download
HTTPCaller_4
    CONNECTION_TIMEOUT_LENGTH = 60
    CUSTOM_HEADERS = Authorization;Basic @Value(_keyAPI)
    ERROR_ATTR = _error
    FILE_PATH_ATTR = _response_file_path
    FOLLOW_REDIRECTS = Yes
    HTTP_METHOD = GET
    OUTPUT_FILENAME = $(zip_output)
    SAVE_FILE = File
    SAVE_MULTI = No
    STATUS_CODE_ATTR = _http_status_code
    TARGET_URL = @Value(link.href)
    TRANSFER_TIMEOUT_LENGTH = 90
    USE_COOKIES = No
    VERIFY_SSL_CERTIFICATES = Yes
    -> Junction

Bookmark: Find the downloaded ZIP archive and unzip it
Junction
    -> FilenamePartExtractor
FilenamePartExtractor
    DIRPATH_ATTR = _dirpath
    SRC_ATTR = @Value(_response_file_path)
    -> ZipExtractor_2
Note: Unzip the downloaded file
ZipExtractor_2
    PRESERVE = No
    RECURSIVE = No
    REPLACE = No
    ROOT_FOLDER = @Value(_dirpath)
    ZIP_PATH = @Value(_response_file_path)
    File -> Tester_4
Note: Filter L2A data
Tester_4
    BOOL_OP = AND
    TEST_CLAUSE:
      CASE_INSENSITIVE_TEST @Value(xml_fragment) CONTAINS _MSIL2A_
      CASE_INSENSITIVE_TEST @Value(path_windows) CONTAINS GRANULE
    TEST_MODE = TEST
    PASSED -> Tester_3
    FAILED -> Tester_5

Bookmark: Split the unzipped images by resolution (Only L2A Product)
Tester_3
    BOOL_OP = OR
    TEST_CLAUSE:
      CASE_SENSITIVE_TEST @Value(path_windows) CONTAINS_REGEX B\d(\d|A)_\d\dm.jp2
      CASE_INSENSITIVE_TEST @Value(path_windows) CONTAINS TCI_10m
    TEST_MODE = TEST
    PASSED -> TestFilter_3
TestFilter_3
    DEFAULT_VALUE = <UNFILTERED>
    TEST_LIST:
      "BOOL_OP,COMPOSITE,COMPOSITE_TEST,""""""1 AND (2 OR 3) AND 4"""""",TEST_CLAUSE,CASE_INSENSITIVE_TEST @Value(path_windows) CONTAINS R10m
      TEST $(Band_Resolution) = 10m
      TEST $(Band_Resolution) = All
      CASE_INSENSITIVE_TEST @Value(path_windows) NOT_CONTAINS TCI_10m",10m,"BOOL_OP,COMPOSITE,COMPOSITE_TEST,""""""1 AND (2 OR (3 AND 4))"""""",TEST_CLAUSE,CASE_INSENSITIVE_TEST @Value(path_windows) CONTAINS R20m
      TEST $(Band_Resolution) = 20m
      TEST $(Band_Resolution) = All
      CASE_SENSITIVE_TEST @Value(path_windows) NOT_CONTAINS_REGEX _B(0[2348]|)_20m.jp2",20m,"BOOL_OP,COMPOSITE,COMPOSITE_TEST,""""""1 AND (2 OR (3 AND (4 AND 5 AND 6)))"""""",TEST_CLAUSE,CASE_INSENSITIVE_TEST @Value(path_windows) CONTAINS R60m
      TEST $(Band_Resolution) = 60m
      TEST $(Band_Resolution) = All
      CASE_SENSITIVE_TEST @Value(path_windows) NOT_CONTAINS_REGEX _B0(2|3|4|5|6|7)_60m.jp2
      CASE_SENSITIVE_TEST @Value(path_windows) NOT_CONTAINS_REGEX _B8A_60m.jp2
      CASE_SENSITIVE_TEST @Value(path_windows) NOT_CONTAINS_REGEX _B1(1|2)_60m.jp2",60m,"BOOL_OP,AND,COMPOSITE_TEST,""""""<Unused>"""""",TEST_CLAUSE,CASE_INSENSITIVE_TEST @Value(path_windows) CONTAINS_REGEX TCI_10m
      TEST $(Band_Resolution) = All",TCI
    10m -> FeatureReader_3 [INITIATOR]
    20m -> FeatureReader_3 [INITIATOR]
    60m -> FeatureReader_3 [INITIATOR]
    TCI -> FeatureReader_3 [INITIATOR]
FeatureReader_3
    ATTRIBUTES = JPEG2000,fme_basename
    ATTR_ACCUM_MODE = Only Use Result
    COMBINE_GEOM = Use Result
    DATASET = @Value(path_unix)
    FORMAT = JPEG2000
    INTERACT = <No Spatial Filter>
    JPEG2000_GROUP_BY_DATASET = No
    JPEG2000_JPEG2000_EXPOSE_FORMAT_ATTRS = fme_basename,char(50)
    JPEG2000_PREFER_FILE_CS_UNITS = Yes
    JPEG2000_READER_META_ATTRIBUTES = fme_dataset fme_basename
    JPEG2000_READ_OFFSETS_IN_CS_UNITS = No
    JPEG2000_USE_SEARCH_ENVELOPE = NO
    OUTPUT_FEATURES_DISPLAY = Schema and Data Features
    JPEG2000 -> TestFilter_4
TestFilter_4
    DEFAULT_VALUE = <UNFILTERED>
    TEST_LIST = "BOOL_OP,OR,COMPOSITE_TEST,""""""<Unused>"""""",TEST_CLAUSE,CASE_SENSITIVE_TEST @Value(fme_basename) CONTAINS_REGEX B01_\d\dm",B01,"BOOL_OP,OR,COMPOSITE_TEST,""""""<Unused>"""""",TEST_CLAUSE,CASE_SENSITIVE_TEST @Value(fme_basename) CONTAINS_REGEX B02_\d\dm",B02,"BOOL_OP,OR,COMPOSITE_TEST,""""""<Unused>"""""",TEST_CLAUSE,CASE_SENSITIVE_TEST @Value(fme_basename) CONTAINS_REGEX B03_\d\dm",B03,"BOOL_OP,OR,COMPOSITE_TEST,""""""<Unused>"""""",TEST_CLAUSE,CASE_SENSITIVE_TEST @Value(fme_basename) CONTAINS_REGEX B04_\d\dm",B04,"BOOL_OP,OR,COMPOSITE_TEST,""""""<Unused>"""""",TEST_CLAUSE,CASE_SENSITIVE_TEST @Value(fme_basename) CONTAINS_REGEX B05_\d\dm",B05,"BOOL_OP,OR,COMPOSITE_TEST,""""""<Unused>"""""",TEST_CLAUSE,CASE_SENSITIVE_TEST @Value(fme_basename) CONTAINS_REGEX B06_\d\dm",B06,"BOOL_OP,OR,COMPOSITE_TEST,""""""<Unused>"""""",TEST_CLAUSE,CASE_SENSITIVE_TEST @Value(fme_basename) CONTAINS_REGEX B07_\d\dm",B07,"BOOL_OP,OR,COMPOSITE_TEST,""""""<Unused>"""""",TEST_CLAUSE,CASE_SENSITIVE_TEST @Value(fme_basename) CONTAINS_REGEX B08_\d\dm",B08,"BOOL_OP,OR,COMPOSITE_TEST,""""""<Unused>"""""",TEST_CLAUSE,CASE_SENSITIVE_TEST @Value(fme_basename) CONTAINS_REGEX B8A_\d\dm",B8A,"BOOL_OP,OR,COMPOSITE_TEST,""""""<Unused>"""""",TEST_CLAUSE,CASE_SENSITIVE_TEST @Value(fme_basename) CONTAINS_REGEX B09_\d\dm",B09,"BOOL_OP,OR,COMPOSITE_TEST,""""""<Unused>"""""",TEST_CLAUSE,CASE_SENSITIVE_TEST @Value(fme_basename) CONTAINS_REGEX B10_\d\dm",B10,"BOOL_OP,OR,COMPOSITE_TEST,""""""<Unused>"""""",TEST_CLAUSE,CASE_SENSITIVE_TEST @Value(fme_basename) CONTAINS_REGEX B11_\d\dm",B11,"BOOL_OP,OR,COMPOSITE_TEST,""""""<Unused>"""""",TEST_CLAUSE,CASE_SENSITIVE_TEST @Value(fme_basename) CONTAINS_REGEX B12_\d\dm",B12,"BOOL_OP,OR,COMPOSITE_TEST,""""""<Unused>"""""",TEST_CLAUSE,CASE_SENSITIVE_TEST @Value(fme_basename) CONTAINS_REGEX TCI_10m",TCI
    B01 -> Band_1 (output)
    B02 -> Band_2 (output)
    B03 -> Band_3 (output)
    B04 -> Band_4 (output)
    B05 -> Band_5 (output)
    B06 -> Band_6 (output)
    B07 -> Band_7 (output)
    B08 -> Band_8 (output)
    B8A -> Band_8A (output)
    B09 -> Band_9 (output)
    B10 -> Band_10 (output)
    B11 -> Band_11 (output)
    B12 -> Band_12 (output)
    TCI -> TCI (output)

Bookmark: output the unzipped images band-wise (L1C Product)
Tester_5
    BOOL_OP = OR
    TEST_CLAUSE:
      CASE_SENSITIVE_TEST @Value(path_windows) CONTAINS_REGEX B\d(\d|A).jp2
      CASE_INSENSITIVE_TEST @Value(path_windows) CONTAINS TCI.jp2
    TEST_MODE = TEST
    PASSED -> TestFilter_6
TestFilter_6
    DEFAULT_VALUE = <UNFILTERED>
    TEST_LIST:
      "BOOL_OP,COMPOSITE,COMPOSITE_TEST,""""""1 AND (2 OR 3)"""""",TEST_CLAUSE,CASE_INSENSITIVE_TEST @Value(path_windows) CONTAINS_REGEX _B0[2348].jp2
      TEST $(Band_Resolution) = 10m
      TEST $(Band_Resolution) = All",10m,"BOOL_OP,COMPOSITE,COMPOSITE_TEST,""""""1 AND (2 OR (3 AND 4))"""""",TEST_CLAUSE,CASE_INSENSITIVE_TEST @Value(path_windows) CONTAINS_REGEX _B((0|8)([567]|A)|11|12).jp2
      TEST $(Band_Resolution) = 20m
      TEST $(Band_Resolution) = All
      CASE_SENSITIVE_TEST @Value(path_windows) NOT_CONTAINS_REGEX _B(0[2348]|).jp2",20m,"BOOL_OP,COMPOSITE,COMPOSITE_TEST,""""""1 AND (2 OR (3 AND (4 AND 5 AND 6)))"""""",TEST_CLAUSE,CASE_INSENSITIVE_TEST @Value(path_windows) CONTAINS_REGEX _B(0[19]|10).jp2
      TEST $(Band_Resolution) = 60m
      TEST $(Band_Resolution) = All
      CASE_SENSITIVE_TEST @Value(path_windows) NOT_CONTAINS_REGEX _B0(2|3|4|5|6|7).jp2
      CASE_SENSITIVE_TEST @Value(path_windows) NOT_CONTAINS_REGEX _B8A.jp2
      CASE_SENSITIVE_TEST @Value(path_windows) NOT_CONTAINS_REGEX _B1(1|2).jp2",60m,"BOOL_OP,AND,COMPOSITE_TEST,""""""<Unused>"""""",TEST_CLAUSE,CASE_INSENSITIVE_TEST @Value(path_windows) CONTAINS_REGEX TCI
      TEST $(Band_Resolution) = All",TCI
    10m -> FeatureReader_2 [INITIATOR]
    20m -> FeatureReader_2 [INITIATOR]
    60m -> FeatureReader_2 [INITIATOR]
    TCI -> FeatureReader_2 [INITIATOR]
FeatureReader_2
    ATTRIBUTES = JPEG2000,fme_basename
    ATTR_ACCUM_MODE = Only Use Result
    COMBINE_GEOM = Use Result
    DATASET = @Value(path_unix)
    FORMAT = JPEG2000
    INTERACT = <No Spatial Filter>
    JPEG2000_GROUP_BY_DATASET = No
    JPEG2000_JPEG2000_EXPOSE_FORMAT_ATTRS = fme_basename,char(50)
    JPEG2000_PREFER_FILE_CS_UNITS = Yes
    JPEG2000_READER_META_ATTRIBUTES = fme_dataset fme_basename
    JPEG2000_READ_OFFSETS_IN_CS_UNITS = No
    JPEG2000_USE_SEARCH_ENVELOPE = NO
    OUTPUT_FEATURES_DISPLAY = Schema and Data Features
    JPEG2000 -> TestFilter_5
TestFilter_5
    DEFAULT_VALUE = <UNFILTERED>
    TEST_LIST = "BOOL_OP,OR,COMPOSITE_TEST,""""""<Unused>"""""",TEST_CLAUSE,CASE_SENSITIVE_TEST @Value(fme_basename) CONTAINS_REGEX B01",B01,"BOOL_OP,OR,COMPOSITE_TEST,""""""<Unused>"""""",TEST_CLAUSE,CASE_SENSITIVE_TEST @Value(fme_basename) CONTAINS_REGEX B02",B02,"BOOL_OP,OR,COMPOSITE_TEST,""""""<Unused>"""""",TEST_CLAUSE,CASE_SENSITIVE_TEST @Value(fme_basename) CONTAINS_REGEX B03",B03,"BOOL_OP,OR,COMPOSITE_TEST,""""""<Unused>"""""",TEST_CLAUSE,CASE_SENSITIVE_TEST @Value(fme_basename) CONTAINS_REGEX B04",B04,"BOOL_OP,OR,COMPOSITE_TEST,""""""<Unused>"""""",TEST_CLAUSE,CASE_SENSITIVE_TEST @Value(fme_basename) CONTAINS_REGEX B05",B05,"BOOL_OP,OR,COMPOSITE_TEST,""""""<Unused>"""""",TEST_CLAUSE,CASE_SENSITIVE_TEST @Value(fme_basename) CONTAINS_REGEX B06",B06,"BOOL_OP,OR,COMPOSITE_TEST,""""""<Unused>"""""",TEST_CLAUSE,CASE_SENSITIVE_TEST @Value(fme_basename) CONTAINS_REGEX B07",B07,"BOOL_OP,OR,COMPOSITE_TEST,""""""<Unused>"""""",TEST_CLAUSE,CASE_SENSITIVE_TEST @Value(fme_basename) CONTAINS_REGEX B08",B08,"BOOL_OP,OR,COMPOSITE_TEST,""""""<Unused>"""""",TEST_CLAUSE,CASE_SENSITIVE_TEST @Value(fme_basename) CONTAINS_REGEX B8A",B8A,"BOOL_OP,OR,COMPOSITE_TEST,""""""<Unused>"""""",TEST_CLAUSE,CASE_SENSITIVE_TEST @Value(fme_basename) CONTAINS_REGEX B09",B09,"BOOL_OP,OR,COMPOSITE_TEST,""""""<Unused>"""""",TEST_CLAUSE,CASE_SENSITIVE_TEST @Value(fme_basename) CONTAINS_REGEX B10",B10,"BOOL_OP,OR,COMPOSITE_TEST,""""""<Unused>"""""",TEST_CLAUSE,CASE_SENSITIVE_TEST @Value(fme_basename) CONTAINS_REGEX B11",B11,"BOOL_OP,OR,COMPOSITE_TEST,""""""<Unused>"""""",TEST_CLAUSE,CASE_SENSITIVE_TEST @Value(fme_basename) CONTAINS_REGEX B12",B12,"BOOL_OP,OR,COMPOSITE_TEST,""""""<Unused>"""""",TEST_CLAUSE,CASE_SENSITIVE_TEST @Value(fme_basename) CONTAINS_REGEX TCI",TCI
    B01 -> Band_1 (output)
    B02 -> Band_2 (output)
    B03 -> Band_3 (output)
    B04 -> Band_4 (output)
    B05 -> Band_5 (output)
    B06 -> Band_6 (output)
    B07 -> Band_7 (output)
    B08 -> Band_8 (output)
    B8A -> Band_8A (output)
    B09 -> Band_9 (output)
    B10 -> Band_10 (output)
    B11 -> Band_11 (output)
    B12 -> Band_12 (output)
    TCI -> TCI (output)
